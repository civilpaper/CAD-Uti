(defun c:bup(/ tm no o_get o_number os i ed basepoint xscale)
  (if (= ly_scale nil) (c:tl))
  (setq tm (getvar "TILEMODE"))
  (if (= tm 0) (setvar "TILEMODE" 1))
  (setq o_get (ssget '((0 . "INSERT"))))
  (setq o_number (sslength o_get))
  (setq no 0)
  (setq os (getvar "OSMODE"))
  (setvar "OSMODE" 0)
  (while (< no o_number)
     (progn
       (setq i (ssname o_get no))
       (setq ed (entget i))
       (if (= (cdr (assoc 0 ed)) "INSERT")
	 (progn
	   (setq basepoint (cdr (assoc 10 (entget i))))
	   (setq xscale (abs (cdr (assoc 41 (entget i)))))
	   (command ".scale" i "" basepoint (/ 1 xscale))
	   (command ".scale" i "" basepoint ly_scale)
	   )
	 )
       (setq no (+ no 1))
       )
    )
  (setvar "OSMODE" os)
  )
;;;;;;;;;;;;;;;;;;;;;;;;;;;;;;;;;;;;;;;;;;;
(defun bup(o_get / tm no o_number os i ed basepoint xscale)
  (if (= ly_scale nil) (c:tl))
  (setq tm (getvar "TILEMODE"))
  (if (= tm 0) (setvar "TILEMODE" 1))
  (setq o_number (sslength o_get))
  (setq no 0)
  (setq os (getvar "OSMODE"))
  (setvar "OSMODE" 0)
  (while (< no o_number)
    (progn
      (setq i (ssname o_get no))
      (setq ed (entget i))
      (if (= (cdr (assoc 0 ed)) "INSERT")
	(progn
	  (setq basepoint (cdr (assoc 10 (entget i))))
	  (setq xscale (abs (cdr (assoc 41 (entget i)))))
	  (command ".scale" i "" basepoint (/ 1 xscale))
	  (command ".scale" i "" basepoint ly_scale)
	)
      )
      (setq no (+ no 1))
    )
  )
  (setvar "OSMODE" os)
)
;;;;;;;;;;;;;;;;;;;;;;;;;;;;;;;;;;;;;;;;;;;
(defun c:sect(/ ss os p1 p2 str1 str2)
  (setq ss (ssadd))
  (setq unit (getvar "INSUNITS"))
  (setvar "INSUNITS" 4)
  (if (= ly_scale nil) (c:tl))
  (setq p1 (getpoint "\nStart:  "))
  (setq p2 (getpoint "\nEnd:  " p1))
  (setq os (getvar "OSMODE"))
  (setvar "OSMODE" 0)
  (setq str1 "-")
  (setq str1 (getstring "\nDrawing Number<->:  "))
  (setq str2 "A")
  (setq str2 (getstring "\nSection Letter<A>:  "))
  (command ".insert" "Section_start.dwg" p1 ly_scale ly_scale "" str1 str2)
  (setq ss (ssadd (entlast) ss))
  (command ".insert" "Section_direction.dwg" p1 ly_scale ly_scale (* (/ (angle p1 p2) pi) 180))
  (setq ss (ssadd (entlast) ss))
  (command ".insert" "Section_end.dwg" p2 ly_scale ly_scale (* (/ (angle p1 p2) pi) 180))
  (setq ss (ssadd (entlast) ss))
  (setvar "OSMODE" os)
  (setvar "INSUNITS" unit)
  (bup ss)
)
;;;;;;;;;;;;;;;;;;;;;;;;;;;;;;;;;;;;;;;;;;
(defun c:secs(/ ss p1 str1 str2 str3)
  (setq ss (ssadd))
  (setq unit (getvar "INSUNITS"))
  (setvar "INSUNITS" 4)
  (if (= ly_scale nil) (c:tl))
  (setq p1 (getpoint "\nStart:  "))
  (setq os (getvar "OSMODE"))
  (setvar "OSMODE" 0)
  (setq str1 "?")
  (setq str1 (getstring "\nEnter Section Letter<?>:  "))
  (setq str2 "1:50")
  (setq str2 (getstring "\nEnter Scale<1:50>:  "))
  (setq str3 "-")
  (setq str3 (getstring "\nEnter Drawing No.<->:  "))
  (command ".insert" "Section_show.dwg" p1 ly_scale ly_scale "" str1 str2 str3)
  (setq ss (ssadd (entlast) ss))
  (bup ss)
  (setvar "OSMODE" os)
  (setvar "INSUNITS" unit)

)
;;;;;;;;;;;;;;;;;;;;;;;;;;;;;;;;;;;;;;;;;;;;;
(defun c:dets(/ ss os unit p1 str1 str2 str3)
  (setq unit (getvar "INSUNITS"))
  (setq ss (ssadd))
  (setvar "INSUNITS" 4)
  (if (= ly_scale nil) (c:tl))
  (setq p1 (getpoint "\nStart:  "))
  (setq os (getvar "OSMODE"))
  (setvar "OSMODE" 0)
  (setq str1 "?")
  (setq str1 (getstring "\nEnter Detail Letter<A>:  "))
  (setq str2 "1:50")
  (setq str2 (getstring "\nEnter Scale<1:50>:  "))
  (setq str3 "-")
  (setq str3 (getstring "\nEnter Drawing No.<->:  "))
  (command ".insert" "Detail_show.dwg" p1 ly_scale ly_scale "" str1 str2 str3)
  (setq ss (ssadd (entlast) ss))
  (bup ss)
  (setvar "OSMODE" os)
  (setvar "INSUNITS" unit)

)
;;;;;;;;;;;;;;;;;;;;;;;;;;;;;;;;;;;;;;;;;;
(defun c:det(/ p1 p2 p3 p4 P5 str1 str2)
  (setq unit (getvar "INSUNITS"))
  (setvar "INSUNITS" 4)
  (if (= ly_scale nil) (c:tl))
  (setq p1 (getpoint "\nStart:  "))
  (setq p2 (getpoint "\nStart:  " p1))
  (setq os (getvar "OSMODE"))
  (setvar "OSMODE" 0)
  (setq ss (ssadd))
  (setq str1 "?")
  (setq str1 (getstring "\nEnter Detail Letter<A>:  "))
  (setq str2 "-")
  (setq str2 (getstring "\nEnter Drawing No.<->:  "))
  (if (<= 0 (- (car p2) (car p1)))
    (progn
      (command ".Pline" p1 p2 "")
      (command ".insert" "Detail_l.dwg" p2 ly_scale ly_scale "" str2 str1)
      (setq ss (ssadd (entlast) ss))
      (bup ss)
    )
  )
  (if (> 0 (- (car p2) (car p1)))
    (progn
      (command ".Pline" p1 p2 "")
      (command ".insert" "Detail_r.dwg" p2 ly_scale ly_scale "" str2 str1)
      (setq ss (ssadd (entlast) ss))
      (bup ss)
    )
  )
  (mt p1 p2)
  (setvar "OSMODE" os)
  (setvar "INSUNITS" unit)
)
;;;;;;;;;;;;;;;;;;;;;;;;;;;;;;;;;;;;;;;;;;;;;;;
(defun c:mt(/ ss p1 p2)
  (setq ss (ssadd))
  (setq unit (getvar "INSUNITS"))
  (setvar "INSUNITS" 4)
  (if (= ly_scale nil) (c:tl))
  (setq p1 (getpoint "\nInsert Point:  "))
  (setq p2 (getpoint "\nDirection:  " p1))
  (command ".insert" "arrow1.5.dwg" p1 ly_scale ly_scale p2)
  (setq ss (ssadd (entlast) ss))
  (bup ss)
  (setvar "INSUNITS" unit)
)
;;;;;;;;;;;;;;;;;;;;;;;;;;;;;;;;;;;;;;;;;;;;;;;
(defun mt(p1 p2)
  (setq ss (ssadd))
  (if (= ly_scale nil) (c:tl))
  (setq unit (getvar "INSUNITS"))
  (setvar "INSUNITS" 4)
  (command ".insert" "arrow1.5.dwg" p1 ly_scale ly_scale p2)
  (setq ss (ssadd (entlast) ss))
  (bup ss)
  (setvar "INSUNITS" unit)
)
;;;;;;;;;;;;;;;;;;;;;;;;;;;;;;;;;;;;;;;;;;;;;;;
(defun USTR (bit msg def spflag / inp nval)
     (if (and def (/= def ""))
          (setq msg (strcat "\n" msg "<" def ">: ")
               inp (getstring spflag msg)
               inp (if (= inp "") def inp)
          )
          (progn
               (if (= " " (substr msg (strlen msg) 1))
                    (setq msg (strcat "\n" (substr msg 1 (1- (strlen msg))) ": "))
                    (setq msg (strcat "\n" msg ": "))
               )
               (if (= bit 1)
                    (while (= "" (setq inp (getstring spflag msg)))
                         (prompt "\nInvalid String.")
                    )
                    (setq inp (getstring spflag msg))
               )
          )
     )
     inp
)
;;;;;;;;;;;;;;;;;;;;;;;;;;;;;;;;;;;;;;;;;;;;;;;;;;;;;;;;;;;;;;;;;;;;;;;;;;;;;;;;;;;;;;;;;
(Defun matsosanh(/ pt cao)
  (prompt "\nKhai báo M\U+1EB7t So Sánh")
  (setq pt (getpoint "\nXác \U+0111\U+1ECBnh \U+0110i\U+1EC3m: "))
  (setq cao (getreal "\nCao \U+0111\U+1ED9 c\U+1EE7a \U+0110i\U+1EC3m: "))
  (setq #mss (- (cadr pt) cao))
)
(defun c:#mss() (matsosanh))
;;;;;;;;;;;;;;;;;;;;;;;;;;;;;;;;;;;;;;;;;;;;;;;;;;;;;;;
(defun c:elevation(/ ss unit cl dz ot pt ptside ang y)
  (if ( = #mss nil) (matsosanh))
  (setq ss (ssadd))
  (setq unit (getvar "INSUNITS"))
  (setvar "INSUNITS" 4)
  (if (= #Bacc nil) (setq #Bacc (getint "\nPh\U+1EA7n th\U+1EADp phân: ")))
  (setq CL (getvar "clayer"))
  (setvar "CLAYER" "0") 	
  (setq DZ (getvar "DIMZIN"))
  (setvar "DIMZIN" 0)
  (setq OT (getvar "ORTHOMODE"))
  (setvar "ORTHOMODE" 0)
  (setq pt (getpoint "\n\U+0110i\U+1EC3m l\U+1EA5y Cao \U+0111\U+1ED9: ")
	ptside (getpoint "\nH\U+01B0\U+1EDBng: " pt)
	ang (angle pt ptside)
  )
  (setq y (- (cadr pt) #mss))
  (cond
    ((> y 0) (setq y (strcat "+" (rtos y 2 #Bacc))))
    ((< y 0) (setq y (rtos y 2 #Bacc)))
    ((= y 0) (setq y "%%p0.00"))
    )
  (setq y (ustr 0 "\nCao \U+0111\U+1ED9 \U+0110i\U+1EC3m là: " y T))
  (if (AND (>= ang 0) (< ang 1.5708)) (command ".INSERT" "Elevation" pt ly_scale ly_scale "0" y))
     ( if	 (AND (>= ang 1.5708) (< ang 3.1416)) (command ".INSERT" "Elevation3" pt ly_scale ly_scale "0" y))
     ( if	 (AND (>= ang 3.1416) (< ang 4.7124)) (command ".INSERT" "Elevation2" pt ly_scale ly_scale "0" y))
     ( if	 (AND (>= ang 4.7124) (< ang 6.2832)) (command ".INSERT" "Elevation1" pt ly_scale ly_scale "0" y))
  (setq ss (ssadd (entlast) ss))
  (bup ss)
  (setvar "DIMZIN" DZ)
  (setvar "ORTHOMODE" OT)
  (setvar "CLAYER" CL)
  (setvar "INSUNITS" unit)
)
(defun c:ev() (c:elevation))
;;;;;;;;;;;;;;;;;;;;;;;;;;;;;;;;;;;;;;;;;;;;;;;;;;;;;;;;;;;;;;;;;;;;;;;;;;;;;;;;;;;;;;;;;

;;; BlockToXref.LSP
;;; Select one or many blocks in a drawing and change them to xrefs
;;; The xrefs needs to be existing before running this command

;;; By Jimmy Bergmark
;;; Copyright (C) 1997-2014 JTB World, All Rights Reserved
;;; Website: www.jtbworld.com
;;; E-mail: info@jtbworld.com

;;; 2000-04-03 - First release
;;; Supports nested blocks, multiple tabs
;;; 2014-12-15 - Updated to work with newer versions of AutoCAD
;;; Tested on AutoCAD 2000 and 2015

(defun c:btx () (c:BlockToXref))
(defun c:BlockToXref (/            errexit      undox
                      olderr       restore      errexitA2k
                      ss ss1 e1 ix path
                      bsl bn bnl bl bt not_ok repl oldvport oldregenmode
                      typ ed layer color ltype ang ins tab oldtab
                     )
  (defun errexit (s)
    (princ "\nError:  ")
    (princ s)
    (restore)
  )

  (defun undox ()
    (setq ss1 nil)
    (setq ss2 nil)
    (setvar "ctab" oldtab)
    (if (> oldcvport 1) (command "._mspace") (command "._pspace"))
    (setvar "cvport" oldcvport)
    (setvar "regenmode" oldregenmode)
    (command "._undo" "_E")
    (setvar "cmdecho" oldcmdecho)
    (setq *error* olderr)
    (princ)
  )

  (setq olderr  *error*
        restore undox
        *error* errexit
  )
  (setq oldcmdecho (getvar "cmdecho"))
  (setq oldtab (getvar "ctab"))
  (setq oldcvport (getvar "cvport"))
  (setq oldregenmode (getvar "regenmode"))
  (setvar "cmdecho" 0)
  (setvar "regenmode" 0)
  (command "._UNDO" "_BE")
  (setq A2k (>= (substr (getvar "ACADVER") 1 2) "15"))
  (if (and A2k (/= (setq ss1 (ssget '((0 . "INSERT")))) nil))
    (progn
      (vl-load-com)
      (setq ix 0)
      (setq bsl nil) ; block selection list
      (setq bnl nil) ; unique block name list
      (repeat (sslength ss1)
        (setq e1 (ssname ss1 ix))
        (setq bn (cdr (assoc 2 (entget e1)))) ; block name
        (setq bl (tblsearch "block" bn)) ; block list bn
        (setq bt (cdr (assoc 70 bl))) ; block type
        (if (and (/= (logand bt 4) 4) (not (member bn bnl))) ; no xrefs and no duplicates
           (setq bnl (cons bn bnl))
        )
        (setq ix (1+ ix))
      ); end repeat

      (foreach bn bnl
        (setq ss1 (ssget "X" (list (cons 0 "INSERT") (cons 2 bn))))
        (setq ix 0)
        (repeat (sslength ss1)
          (setq e1 (ssname ss1 ix))
          (setq bsl (cons (entget e1) bsl))
          (setq ix (1+ ix))
        )
      ); end repeat

      (foreach bn bnl
        (setq not_ok T)
        (while not_ok
          (setq path (getfiled "Match the block to a file"
                               (if (not path) (strcat (getvar "dwgprefix") bn) (strcat (vl-filename-directory path) "\\" bn))
                               "dwg" 0))
          (if path
            (if (= (strcase (vl-filename-base  path)) (strcase bn))
              (setq not_ok nil)
              (progn
                (initget 0 "Yes No")
                (setq repl (getkword "\nAssign a different name? [Yes/No] <No>: "))
                (if (not repl) (setq repl "Yes"))
                (if (= "Yes" repl)
                  (setq not_ok nil)
                  (setq not_ok T)
                )
              )        
            )
          )
          (if (not not_ok)
            (progn
              (setq ss (ssget "X" (list (cons 0 "INSERT") (cons 2 bn))))
              (setq ix 0)
              (repeat (sslength ss)
                (setq ed (ssname ss ix))
                (setq tab (cdr (assoc 410 (entget ed))))
                (setvar "ctab" tab)
                (entdel ed)
                (setq ix (1+ ix))
              )
              (repeat 10
                (vl-cmdf "._purge" "_b" "*" "N")
              )
              (initget 0 "Overlay Attach")
              (setq repl (getkword "\nEnter an option [Overlay/Attach] <Attach>: "))
              (if (not repl) (setq repl "Attach"))
              (if (= "Attach" repl) (setq typ "_A") (setq typ "_O"))
              (setq ix 0)
              (repeat (length bsl)
                (setq ed (nth ix bsl))
                (if (= bn (cdr (assoc 2 ed)))
                  (progn
                    (setq layer (cdr (assoc 8 ed)))
                    (setq color (cdr (assoc 62 ed)))
                    (if (not color) (setq color "_ByLayer"))
                    (setq ltype (cdr (assoc 6 ed)))
                    (if (not ltype) (setq ltype "_ByLayer"))
                    (setq ang (/ (* 180.0 (cdr (assoc 50 ed))) pi))
                    (setq ins (cdr (assoc 10 ed)))
                    (setq tab (cdr (assoc 410 ed)))
                    (setvar "ctab" tab)
                    (if (/= tab "Model") (command "._pspace"))
                    (vl-cmdf "._xref" typ path "_X" (cdr (assoc 41 ed)) "_Y" (cdr (assoc 42 ed)) "_Z" (cdr (assoc 43 ed)) ins ang)
                    (vl-cmdf "._change" "_L" "" "_P" "_C" color "_LA" layer "_LT" ltype "")
                  )
                )
                (setq ix (1+ ix))
              )
            )
          )
          (if (= path nil) (setq not_ok nil))
        )
      )
    ); end progn
  ); end if
  (setq ss1 nil)
  (restore)
)
